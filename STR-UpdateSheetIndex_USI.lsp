;; UPDATE SHEET INDEX BASED ON DRAWING INFORMATION AND SHEETS AVAILABLE

(defun c:USI ( / )
	(ECHO:LogWrapper "STR-UpdateSheetIndex_USI.lsp" "USI" UpdateSheetIndexMain)
)

(defun c:UPDATESHEETINDEX ( / )
	(ECHO:LogWrapper "STR-UpdateSheetIndex_USI.lsp" "UPDATESHEETINDEX" UpdateSheetIndexMain)
)


(defun UpdateSheetIndexMain
	(
		/
		;Functions
		*error* ClearTableObject MappedLayoutList
		GetTitleBlock ReturnAttributeValue ReturnLastAttributeValue
		;Variables
		tbl row tblk ttl
	)
	
	(defun *error* ( msg )
		(if (not (member msg (list "Function cancelled" "quit / exit abort")))
			(vl-bt)
		)
		(ECHO:Log "ERROR" msg nil (list (cons "CMDNAME" *ECHO:Log-Command*)))
		(ECHO:Log-Flush)
		(strcat "\nError: " msg)
	)
	
	(defun ClearTableObject ( tbl row )
	  	(if (> (vla-get-rows tbl) row)
			(vla-deleterows tbl row (1- (vla-get-rows tbl)))
		)
	)
	;; DELETE A PASSED TABLE OBJECTS ROWS STARTING AT A PASSED ROW (INTEGER)
	
	(defun MappedLayoutList ( / lst )
		(vlax-for lyt (vla-get-layouts (vla-get-activedocument (vlax-get-acad-object)))
			(setq lst (cons (cons (vla-get-name lyt) lyt) lst))
		)
		(cdr (vl-sort lst '(lambda ( x y ) (< (vla-get-taborder (cdr x)) (vla-get-taborder (cdr y))))))
	)
	;; RETURNS MAPPED LIST OF LAYOUT NAMES WITH THE CORRECPONDING LAYOUT OBJECTS (EXCLUDES "MODEL")
	
	(defun GetTitleBlock ( sht / sel )
		(if (setq sel (ssget "_X" (list (cons 0 "INSERT") (cons 2 "*Title Block*") (cons 410 sht))))
			(vlax-ename->vla-object (cadar (ssnamex sel)))
		)
	)
	;; RETURNS TITLE BLOCK OBJECT BASSED ON PASSED STRING "SHT"
	
	(defun ReturnAttributeValue ( blk str )
		(if (eq :vlax-true (vla-get-hasattributes blk))
			(car
				(vl-remove 'nil
					(mapcar
						'(lambda ( att )
							(if (eq str (vla-get-tagstring att))
								(vla-get-textstring att)
							)
						)
						(vlax-safearray->list (vlax-variant-value (vla-getattributes blk)))
					)
				)
			)
		)
	)
	;; RETURNS ATTRIBUTE VALUE OF PASSED STRING (STR) IN PASSED BLOCK OBJECT (BLK) IF IT EXISTS
	
	(defun ReturnLastAttributeValue ( blk att / ptn )
		(setq ptn (strcat att "*"))
		(if (eq :vlax-true (vla-get-hasattributes blk))
			(last
				(vl-remove 'nil
					(mapcar
						'(lambda ( a )
							(if (wcmatch (vla-get-tagstring a) ptn)
								(if (/= (vla-get-textstring a) "")
									(vla-get-tagstring a)
								)
							)
						)
						(vlax-safearray->list (vlax-variant-value (vla-getattributes blk)))
					)
				)
			)
		)
	)
	;; SEARCHES A PASSED BLOCK FOR A MATCHING ATTRIBUTE TAG PATTERN AND RETURNS THE LATEST ATTRIBUTE TAG THAT IS NULL IF FOUND
	;; !!NOT USED BUT SAVED FOR REFERENCE!!
	
	
	(if (and
			(setq tbl (ssget "_X" (list (cons 0 "ACAD_TABLE") (cons 1 "*SHEET INDEX*"))));"{\\fArial|b1|i0|c0|p34;DRAWING SET LIST}"
			(setq tbl (vlax-ename->vla-object (cadar (ssnamex tbl))))
			(not (vl-catch-all-error-p (vl-catch-all-apply 'ClearTableObject (list tbl (setq row 2)))))
		)
		(foreach lyt (MappedLayoutList)
			(vla-insertrows tbl (1+ row) 0.4013 1)
			(vla-settext tbl row 0 (car lyt))
			(if (setq tblk (GetTitleBlock (car lyt)))
				(vla-settext tbl row 1 (if (null (setq ttl (ReturnAttributeValue tblk "SHEET_TITLE"))) "XXXXX" ttl))
				(vla-settext tbl row 1 "XXXXX") ;; TITLE BLOCK NOT FOUND
			)
			(setq row (1+ row))
		)
		(prompt "\n'Sheet Index' table not found.")
	)
	
	(princ)
)


(Load:DescriptionLog "UPDATESHEETINDEX / USI" "Updates the sheet index table")

;(vla-DeleteRows tbl 2 (1- (vla-get-rows tbl)))
;(vla-insertrows tbl row hgt 1)
